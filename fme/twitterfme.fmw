FME workspace twitterfme.fmw

Creator
    GEOMTYPE = Geometry Object
    GEOM = <?xml version="1.0" encoding="US_ASCII" standalone="no" ?><geometry><polygon><line><coord x="-180" y="-90"/><coord x="180" y="-90"/><coord x="180" y="90"/><coord x="-180" y="90"/><coord x="-180" y="-90"/></line></polygon></geometry>
    NUM = 1
    COORDSYS = EPSG:4326
    CREATED -> TweetStreamer
TweetStreamer
    USE_GEOMETRY = Yes
    TWITTER_PASSWORD =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
    HTTP_PROXY_AUTH_METHOD = Basic
    POINT_BUFFER = 3
    TWITTER_USERNAME = fmecloud
    TWEETS -> JSONFlattener
JSONFlattener
    JSON_ATTR = _tweet_search_result
    NEW_ATTRIBUTES = coordinates.coordinates{0} coordinates.coordinates{1} coordinates place.full_name text retweet_count user.followers_count source
    RECURSIVE = Yes
    -> Tester
Tester
    TEST_MODE = Automatic
    BOOL_OP = OR
    TEST_DESCRIPTION = ""
    TEST_CLAUSE = TEST @Value(coordinates.coordinates{0}) != ""
    PASSED -> VertexCreator
VertexCreator
    YVAL = @Value(coordinates.coordinates{1})
    XVAL = @Value(coordinates.coordinates{0})
    MODE_NAME = Add Point
    -> StringConcatenator
StringConcatenator
    VAL_ATTR = _concatenated
    PARM_LINE = {"lat": "@Value(coordinates.coordinates{0})","lng": "@Value(coordinates.coordinates{1})"}
    -> WebSocketSender
WebSocketSender
    DATA:
      {
          ws_op: 'send',
          ws_msg: '@Value(_concatenated)'
      }
    HOST = wss://localhost:7078
    PREAMBLE:
      {
         ws_op : 'open',
         ws_stream_id : 'twitter-stream-out'
      }
